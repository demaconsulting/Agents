// <!-- TEMPLATE-DIRECTIVE:
//      Read the sysml2-modeling.md standard before editing this file. Model shared package
//      dependencies used by the system(s) in this repository, mirroring
//      docs/design/shared/{package-name}.md files. Add one `part def` per shared package.
//      Replace SystemName and PackageName with your actual names (PascalCase). This file
//      is OPTIONAL - remove it (and its import in {system-name}.sysml) if the project has
//      no shared package dependencies. -->
package SharedPackages {
    doc /* Shared package dependencies used by SystemName. */

    // <!-- TEMPLATE-DIRECTIVE: One `part def` per shared package. -->
    part def PackageName {
        doc /* Shared: PackageName - TODO: one sentence describing its purpose here. */
    }
}
